-- *****************************************************************
-- This file is in the public domain.
--
-- FreeBSD SMI { enterprises 2238 }
--
-- $FreeBSD: releng/11.1/share/snmp/mibs/FREEBSD-MIB.txt 163822 2006-10-31 10:09:10Z harti $
--
-- *****************************************************************

FREEBSD-MIB DEFINITIONS ::= BEGIN

IMPORTS
	MODULE-IDENTITY,
	OBJECT-IDENTITY,
	enterprises
		FROM SNMPv2-SMI;

freeBSD MODULE-IDENTITY
	LAST-UPDATED "200610311000Z"
	ORGANIZATION "The FreeBSD Project."
	CONTACT-INFO
		"phk@FreeBSD.org is contact person for this file.
		 core@FreeBSD.org is the final authority."
	DESCRIPTION
		"The Structure of Management Information for the
		FreeBSD Project enterprise MIB subtree."
	REVISION      "200610310800Z"
	DESCRIPTION
		"Initial version of this MIB module."
	::= { enterprises 2238 }	-- assigned by IANA


freeBSDsrc OBJECT-IDENTITY
	STATUS	current
	DESCRIPTION
		"Subtree for things which lives in the src tree."
	::= { freeBSD 1 }

freeBSDports OBJECT-IDENTITY
	STATUS	current
	DESCRIPTION
		"Subtree for things which lives in the ports tree."
	::= { freeBSD 2 }

freeBSDpeople OBJECT-IDENTITY
	STATUS	current
	DESCRIPTION
		"Subtree for FreeBSD people.
		 Under this branch any FreeBSD committer may claim
		 a subtree.  Grab the next sequential oid in the list.
		 These assignments are not revoked when committers leave
		 the FreeBSD project.
		"
	::= { freeBSD 3 }

freeBSDpeoplePhk OBJECT-IDENTITY
	STATUS current DESCRIPTION
		"Subtree for phk@FreeBSD.org"
	::= {freeBSDpeople 1}

freeBSDVersion OBJECT-IDENTITY
	STATUS	current
	DESCRIPTION
		"Subtree to register FreeBSD versions. The OID for a FreeBSD
		 version is formed by appending the dot delimited numbers
		 from the release number to this base OID. Examples:

		  5.2.1-STABLE:	freeBSDVersion.5.2.1
		  6.1-STABLE:	freeBSDVersion.6.1
		  7.0-CURRENT:	freeBSDVersion.7.0

		 There is no indication whether this is STABLE or CURRENT.

		 The sysObjectId is automatically set to the value indicated
		 by the uname(3) release field by bsnmpd(1). This initial
		 value can be overwritten in the configuration file."
	::= { freeBSD 4 }

END
